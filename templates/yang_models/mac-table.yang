module mac-table {
    namespace "urn:mac-table";
    prefix "mac-table";

    container mac {
        
        list mac-entry {
            key "mac-address";

            leaf mac-address {
                type string;
                description "The MAC address";
            }

            leaf timer {
                type uint32;
                description "The timer value";
            }
            
            leaf port {
                type string;
                description "The port the MAC address is associated with";
            }

            leaf last_seen {
                type uint64;
                description "The Unix timestamp when the MAC address was last seen";
            }
        }

    }
}
