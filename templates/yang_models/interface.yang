module interface {
    namespace "urn:interface";
    prefix "if";

    container interfaces {
        list interface-entry {
            key "name";
            
            leaf name {
                type string;
                description "Name of the interface";
            }
            leaf state {
                type string;
                description "State of the interface";
            }
        }
    }
}
